module fpcpagent {
    namespace "urn:ietf:params:xml:ns:yang:fpcpagent";
    prefix fpcp-base;

    import ietf-inet-types { prefix inet; revision-date 2013-07-15; }

    organization "IETF DMM Working Group";
    contact "Satoru Matsushima <satoru.matsushima@g.softbank.co.jp>";

    description
    "This module contains YANG definition for
     Forwarding Policy Configuration Protocol.(FPCP)";

    revision 2016-23-07 {
        description "Changes based on -03 version of FPCP draft.";
        reference "draft-ietf-dmm-fpc-cpdp-01";
    }

    typedef fpcp-name-type {
        type string;
        description "FPCP common name type";
    }

    // Descriptor Structure
    typedef fpc-descriptor-id {
        type uint32;
        description "Rule-ID";
    }

    identity fpc-descriptor-type {
        description
          "A traffic descriptor";
    }

    grouping fpc-descriptor {
        leaf descriptor-type {
          type identityref {
            base "fpc-descriptor-type";
          }
          description "Descriptor Type";
        }
        choice descriptor-value {
          case all-traffic {
            leaf all-traffic {
              type empty;
            }
          }
        }
    }

    // Action Structure
    typedef fpc-action-id {
        type uint32;
        description "Rule-ID";
    }

    identity fpc-action-type {
        base
          "Action Type";
    }

    grouping fpc-action {
        leaf action-type {
          type identityref {
            base "fpc-action-type";
          }
          description "Action Type";
        }
        choice action-value {
          case drop {
            leaf drop {
              type empty;
            }
          }
        }
    }


    typedef fpc-rule-id {
        type uint32;
        description "Rule-ID";
    }


    typedef fpcp-rule-id {
        type uint32;
        description "Rule-ID";
    }

    // Figure 6
    typedef fpcp-carrier-id {
        type uint16;
        description "Carrier-ID";
    }

    typedef fpcp-network-id {
        type uint16;
        description "Carrier-ID";
    }

    typedef fpcp-client-id {
        type uint32;
        description "Client-ID";
    }

    typedef fpcp-agent-id {
        type uint32;
        description "Agent-ID";
    }

    typedef fpcp-dpn-id {
        type uint32;
        description "Carrier-ID";
    }

    typedef fpcp-port-id {
        type uint32;
        description "PRT_ID";
    }

    typedef port_group_id {
        type uint32;
        description "PRT_GROUP_ID";
    }

    typedef fpcp-property-id {
        type uint8;
        description "PRT_PROP_ID";
    }

    typedef fpcp-td-id {
        type uint8;
        description "TD_ID";
    }

    typedef fpcp-monitor-id {
        type uint32;
        description "MONITOR_ID";
    }

    typedef fpcp-event-type-id {
        type uint8;
        description "EVENT_TYPE_ID";
    }

    typedef fpcp-service-path-id {
        type uint32 {
            range "0..33554431";
        }
        description "SERVICE_PATH_ID";
    }

    // Deviation
    typedef fpcp-vrf-id {
        type uint32;
    }



    // Figure 4 - Admin Data
    typedef fpcp-administrative-state {
        type enumeration {
            enum enabled;
            enum disabled;
            enum virtual;
        }
    }

    typedef fpcp-session-state {
        type enumeration {
            enum complete;
            enum incomplete;
            enum outdated;
        }
    }

    // Figure 5
    typedef fpcp-operational-state {
        type enumeration {
            enum up;
            enum down;
            enum error;
            enum unknown;
        }
    }

    typedef fpcp-service-state {
        type enumeration {
            enum complete;
            enum incomplete;
            enum outdated;
        }
    }

    //
    typedef fpcp-qos-class-identifier {
        type uint8 {
            range "1..9";
        }
        description "QCI";
    }

    typedef fpcp-qos-bandwidth {
        type uint32;
        description "Bandwith value in bit per second.";
    }

    identity tunnel-type {
        description
        "Base identity from which specific use of
         tunnels are derived.";
    }

    identity fpcp-tunnel-type {
        base "tunnel-type";
        description
        "Base identity from which specific tunnel
         types in FPCP uses are derived.";
    }

    identity ip-in-ip {
        base "fpcp-tunnel-type";
        description "IP-in-IP tunnel";
    }

    identity gtp {
        base "fpcp-tunnel-type";
        description "GTP-U tunnel";
    }

    identity gre {
        base "fpcp-tunnel-type";
        description "GRE tunnel";
    }

    identity service-function {
        description
        "Base identity from which specific
         service function types are derived.";
    }

    identity ip-protocol {
        description
        "Base identity from which specific
         IP protocol types are derived.";
    }

    identity property-type {
        description
        "Base identity of property";
    }

    identity property-qos {
        base "property-type";
        description
        "QoS property";
    }

    identity property-endpoint {
        base "property-type";
        description
        "Endpoint property";
    }

    // Deviation Start

    identity property-dpns {
        base "property-type";
        description
          "attached DPNs";
    }

    identity property-drop {
        base "property-type";
        description
            "drop action";
    }

    identity property-next-hop {
        base "property-type";
        description
          "Next Hop";
    }

    identity property-assigned-ip {
        base "property-type";
        description
          "Assigned IP Address";
    }

    identity property-concat {
        base "property-type";
        description
          "Property Action Concatenation";
    }

    identity property-service-path {
        base "property-type";
        description
            "Newtork Service Header";
    }

    identity property-vrf {
        base "property-type";
        description
          "Virtual Routing and Forwarding Identifier";
    }

    identity property-operational-state {
        base "property-type";
        description
          "Operational State Property";
    }

    identity property-administrative-state {
        base "property-type";
        description
          "Administrative state property";
    }

    identity property-rewriting {
        base "property-type";
        description
          "Rewriting Property";
    }

    identity property-bidirectional {
        base "property-type";
        description
          "Property Action Concatenation";
    }

    identity property-cipa {
        base "property-type";
        description
          "CIPA";
    }

    // Deviation End

    identity qos-type {
        description
        "Base identity from which specific
         uses of QoS types are derived.";
    }

    identity fpcp-qos-type {
        base "qos-type";
        description
        "Base identity from which specific
         QoS types in FPCP uses are derived.";
    }

    identity fpcp-qos-type-gbr {
        base "fpcp-qos-type";
        description
        "A QoS Type for Guaranteed Bit Rate (GBR).";
    }

    identity fpcp-qos-type-mbr {
        base "fpcp-qos-type";
        description
        "A QoS Type for Maximum Bit Rate (MBR).";
    }

    identity fpcp-qos-index-type {
        base "qos-type";
    }

    // ? Should this be fpcp-qci-index ?
    identity fpcp-qos-index {
        base "fpcp-qos-index-type";
    }

    // DEVIATION FROM THE SPEC
    identity fpcp-profile-reference {
        base "fpcp-qos-index-type";
    }

    identity traffic-descriptor-type {
    }

    identity prefix-descriptor-type {
        base "traffic-descriptor-type";
    }

    // DEVIATION FROM THE SPEC

    identity descriptor-reference {
        base "traffic-descriptor-type";
    }

    // End of deviations

    grouping carrier {
        description "Identify FPCP Carrier";
        leaf carrier-id {
            type fpcp-carrier-id;
            mandatory true;
            description "Carrier ID";
        }
    }

    grouping agent {
        description "AGT_ID to identify FPCP Agent";
        leaf agent-id {
            type fpcp-agent-id;
            description "Agent ID";
        }
    }

    grouping client {
        description "CLI_ID to identify FPCP Client";
        leaf client-id {
            type fpcp-client-id;
            description "Client ID";
        }
    }

    grouping network {
        description "Identify FPCP Network";
        leaf network-id {
            type fpcp-network-id;
            description "Network ID";
        }
    }

    grouping dpn {
        description "Identify FPCP Data-Plane Node";
        leaf dpn-id {
            type fpcp-dpn-id;
            description "DPN ID";
        }
    }

    grouping port {
        description "Identify FPCP Port";
        leaf port-id {
            type fpcp-port-id;
            description "Port-ID";
        }
    }

    grouping property {
        description "Identify FPCP Property";
        leaf property-id {
            type fpcp-property-id;
            description "Property-ID";
        }
    }

    grouping rule {
        description "Identify FPCP Rule";
        leaf rule-id {
            type fpcp-rule-id;
            description "Rule-ID";
        }
    }

    grouping fpcp-carrier {
        description "Define FPCP network";
        uses carrier;
        uses agent;
        list client {
            key client-id;
            description "List of FPCP Clients";
            leaf name {
                type fpcp-name-type;
                description "Client Name";
            }
            uses client;
        }
        list dpn {
            key dpn-id;
            description "List of FPCP DPNs";
            leaf name {
                type fpcp-name-type;
                description "DPN Name";
            }
            uses dpn;
        }
    }

    grouping dpn-set {
        description "DPNs which consist a DPN set.";
        leaf name {
            type fpcp-name-type;
            description "DPN set name";
        }
        leaf network {
            type leafref {
                path "/fpcp-carriers/carrier/network/network-id";
            }
            description "Network-ID which a DPN-set is belonging to.";
        }
        leaf role {
            type enumeration {
                enum anchor-l3 {
                    description "";
                }
                enum anchor-l2 {
                    description "";
                }
                enum access {
                    description "";
                }
            }
            description "Define DPNs role in data-plane.";
        }
        list endpoint-dp {
            key local-address;
            description "List of data-plane endpoint properties of a set of DPNs.";
            leaf local-address {
                type inet:ip-address;
                description "";
            }
            leaf remote-dpn {
                type leafref {
                    path "/fpcp-carriers/carrier/dpn-group/name";
                }
                description "";
            }
            leaf default-tunnel-type {
                type identityref {
                    base "fpcp-tunnel-type";
                }
                description "Tunnel Type";
            }
        }
        list dpn {
            key dpn-id;
            uses dpn;
            description "DPN list in a DPN set";
        }
    }

    grouping tunnel-endpoints {
        description
        "PROP_TUN property as a set of tunnel endpoints";
        leaf tunnel-type {
            type identityref {
                base "fpcp-tunnel-type";
            }
            description "Tunnel Type";
        }
        leaf remote-address {
            type inet:ip-address;
            description "Remote endpoint";
        }
        leaf local-address {
            type inet:ip-address;
            description "Local endpoint";
        }
    }

    grouping gtp-attributes {
        description
        "GTP_CONF as GTP tunnel specific attributes";
        leaf remote-teid {
            type uint32;
            description "TEID of remote-endpoint";
        }
        leaf local-teid {
            type uint32;
            description "TEID of local-endpoint";
        }
    }

    grouping gre-attributes {
        description
        "GRE_CONF as GRE tunnel specific attribute";
        leaf key {
            type uint32;
            description "GRE_KEY";
        }
    }

    identity napt-service {
        base "service-function";
    }

    identity nat-service {
        base "service-function";
    }

    grouping rewriting-properties {
        description
        "PROP_REWR. TBD for which type of rewriting functions
         need to be defined";
        leaf type {
            type identityref {
                base service-function;
            }
            description "The type of service-function";
        }
        choice value {
            case simple-nat {
                leaf outbound-nat-address {
                    type inet:ip-address;
                }
            }
            case simple-napt {
                leaf source-port {
                    type inet:port-number;
                }
                leaf outbound-napt-address {
                    type inet:ip-address;
                }
                leaf destination-port {
                    type inet:port-number;
                }
            }
        }
    }

    grouping fpcp-qosattribute {
        leaf qci {
            type fpcp-qos-class-identifier;
        }
        leaf attributetype {
            type identityref {
                base fpcp-qos-type;
            }
            description "the attribute type";
        }
        leaf bandwidth {
            type fpcp-qos-bandwidth;
        }
    }

    grouping fpcp-qos-property {
        description "PROP_QOS";
        leaf name {
            type fpcp-name-type;
        }
        leaf qos-index-type {
            type identityref {
                base "fpcp-qos-index-type";
            }
        }
        choice index-type {
            case qci {
                when "../qos-index-type = 'fpcp-qos-index'";
                container uplink {
                    uses fpcp-qosattribute;
                }
                container downlink {
                    uses fpcp-qosattribute;
                }
            }
        }
    }

    grouping prefix-traffic-descriptor {
        description
        "Traffic descriptor group collects parameters to
         identify target traffic flow.  It represents
         source/destination as IP prefixes";

        leaf destination-ip {
            type inet:ip-prefix;
            description "Rule of destination IP";
        }
        leaf source-ip {
            type inet:ip-prefix;
            description "Rule of source IP";
        }
    }

    grouping fpcp-traffic-descriptor {
        leaf name {
            mandatory true;
            type fpcp-name-type;
        }
        leaf descriptor-type {
            type identityref {
                base "traffic-descriptor-type";
            }
        }

        choice descriptor-value {
            case traffic-descriptor-case {
                when "../descriptor-type = 'prefix-descriptor-type'";
                uses prefix-traffic-descriptor;
            }
        }
    }

    grouping fpcp-forwarding-rule {
        uses rule;
        uses fpcp-traffic-descriptor;
    }

    // Deviation from Spec - START
    grouping descriptor-reference-type {
        leaf descriptor-link {
            mandatory true;
            type fpcp-name-type;
        }
    }

    augment "/port-entries/port-entry/forwarding-rule/descriptor-value" {
        case port-td-reference-case {
            when "../descriptor-type = 'descriptor-reference'";
            uses descriptor-reference-type;
        }
    }

    augment "/rule_add/input/adding-rule/forwarding-rule/descriptor-value" {
        case port-td-reference-case {
            when "../descriptor-type = 'descriptor-reference'";
            uses descriptor-reference-type;
        }
    }

    augment "/rule_modify/input/modifying-rule/forwarding-rule/descriptor-value" {
        case port-td-reference-case {
            when "../descriptor-type = 'descriptor-reference'";
            uses descriptor-reference-type;
        }
    }

    // Deviation from Spec - END

    grouping fpcp-port-properties {
        description
        "A set of port property attributes";

        uses property;
        // Deviation from spec - START
        leaf property-type {
            type identityref {
                base "property-type";
            }
        }

        choice value {
            case administrative-state {
                leaf administrative-state {
                    type fpcp-administrative-state;
                }
            }
            case drop {
                leaf drop {
                    type empty;
                }
            }
            case operational-status {
                leaf operational-status {
                    config "false";
                    type fpcp-operational-state;
                }
            }
            case concat {
                leaf-list concat {
                    type leafref {
                        path "/port-entries/port-entry/port-id";
                    }
                }
            }
            case assigned-ip {
                leaf assigned-ip {
                    type inet:ip-address;
                }
            }
            case bidirectional {
                leaf bidirectional {
                    type empty;
                }
            }
            case next-hop {
                leaf next-hop {
                    type inet:ip-address;
                }
            }
            case service-path {
              leaf service-path {
                  type fpcp-service-path-id;
              }
            }
            case vrf {
              leaf vrf {
                  type fpcp-vrf-id;
              }
            }
            case cipa {
              leaf cipa {
                  type empty;
              }
            }
          // Deviation from spec - END
            case attached-dpns {
              list attached-dpns {
                  key name;
                  leaf name {
                      type fpcp-name-type;
                      description "DPN group name of which port attached.";
                  }
                  description "Port attached DPN group list.";
              }
            }
            case endpoints {
              container endpoints {
                  description "Tunnel Endpoint";
                  uses tunnel-endpoints;
                  choice tunnel {
                      description "Tunnel-Type";
                      case gtp-u {
                          when "tunnel-type = 'gtp'" {
                              description "In case of GTP-U is tunnel-type";
                          }
                          uses gtp-attributes;
                      }
                      case gre {
                          when "tunnel-type = 'gre'" {
                              description "In case of GRE is tunnel-type";
                          }
                          uses gre-attributes;
                      }
                  }
              }
           }
           case qos {
              container qos {
                  description "QoS Type";
                  uses fpcp-qos-property;
                  list port-in-aggregated-bandwidth {
                      key port-id;
                      uses port;
                  }
              }
           }
           case rewriting {
              container rewriting {
                  uses rewriting-properties;
              }
           }
        }
    }

    // Deviation from spec - START
    grouping profile-link-group {
        leaf profile-link {
            mandatory true;
            type fpcp-name-type;
        }
    }

    augment "/port-entries/port-entry/property/value/qos/qos/index-type" {
        case port-qos-reference-case {
            when "../qos-index-type = 'fpcp-profile-reference'";
            uses profile-link-group;
        }
    }

    augment "/port_add/input/adding-port/property/value/qos/qos/index-type" {
        case port-qos-reference-case {
            when "../qos-index-type = 'fpcp-profile-reference'";
            uses profile-link-group;
        }
    }

    augment "/port_property_add/input/adding-property/property/value/qos/qos/index-type" {
        case port-qos-reference-case {
            when "../qos-index-type = 'fpcp-profile-reference'";
            uses profile-link-group;
        }
    }

    augment "/port_property_modify/input/modifying-property/property/value/qos/qos/index-type" {
        case port-qos-reference-case {
            when "../qos-index-type = 'fpcp-profile-reference'";
            uses profile-link-group;
        }
    }

    // Deviation from spec - END

    grouping port-field {
        description "Definition of attributes of port field";
        uses port;
        uses carrier;
        uses network;
    }

    // Container for configurations sets.

    container fpcp-carriers {
        description "Attributes set of FPCP network";

        list carrier {
            key carrier-id;
            description "List of carriers";
            leaf name {
                type fpcp-name-type;
                description "FPCP Carrier name";
            }
            uses fpcp-carrier;
            list network {
                key network-id;
                description "List of networks in a carrier.";
                leaf name {
                    type fpcp-name-type;
                    description "Define visible name of a network.";
                }
                uses network;
            }
            list dpn-group {
                key name;
                description "List of DPN groups in a carrier.";
                uses dpn-set;
            }
            list qos-profile {
                key name;
                uses fpcp-qos-property;
            }
            list traffic-descriptor {
                key name;
                uses fpcp-traffic-descriptor;
            }
        }
    }

    // Port Entries

    container port-entries {
        //config false;
        description
        "This container binds set of traffic-descriptor and
         port properties to a port and lists them as a port entry.";

        list port-entry {
            key port-id;
            description "List of port entries";
            uses port-field;

            list property {
                key property-id;
                description "Attributes set of properties";
                uses fpcp-port-properties;
            }

            list forwarding-rule {
                key rule-id;
                description "Rule and traffic-descriptor";
                uses fpcp-forwarding-rule;
            }
        }
    }

    // PRT_ADD

    rpc port_add {
        description "PRT_ADD";
        input {
            list adding-port {
                description "Ports that are added to an agent";
                uses port-field;
                list forwarding-rule {
                    key rule-id;
                    description "Rule and traffic-descriptor";
                    uses fpcp-forwarding-rule;
                }
                list property {
                    key property-id;
                    description "Attributes set of properties";
                    uses fpcp-port-properties;
                }
            }
        }
    }

    // PRT_DEL

    rpc port_delete {
        description "PRT_DEL";
        input {
            list deleting-port {
                description "Ports that are deleted from an agent";
                uses port-field;
            }
        }
    }

    // PROP_ADD

    rpc port_property_add {
        description "PROP_ADD";
        input {
            list adding-property {
                description "Properties that are added to an agent";
                uses port-field;

                list property {
                    key property-id;
                    description "Attributes set of properties";
                    uses fpcp-port-properties;
                }
            }
        }
    }

    // PROP_MOD

    rpc port_property_modify {
        description "PROP_MOD";
        input {
            list modifying-property {
                description
                "Properties that are modified in an agent";
                uses port-field;

                list property {
                    key property-id;
                    description "Attributes set of properties";
                    uses fpcp-port-properties;
                }
            }
        }
    }

    // PROP_DEL

    rpc port_property_delete {
        description "PROP_DEL";
        input {
            list deleting-property {
                description
                "Target port/property-id of deleting properties";
                uses port-field;

                leaf property-id {
                    type fpcp-property-id;
                    mandatory true;
                    description "Property ID";
                }
            }
        }
    }

    // RULE_ADD

    rpc rule_add {
        description
        "TBD for input parameters of which RULE_ADD includes
         but now just traffic-descriptor.";
        input {
            list adding-rule {
                description "Rules that are added to an agent";
                uses port-field;

                list forwarding-rule {
                    description "Added rule";
                    uses fpcp-forwarding-rule;
                }
            }
        }
    }

    // RULE_MOD

    rpc rule_modify {
        description
        "TBD for input parameters of which RULE_MOD includes
         but now just traffic-descriptor.";
        input {
            list modifying-rule {
                description "Rules that are modified in an agent";
                uses port-field;

                list forwarding-rule {
                    description "Modified rule";
                    uses fpcp-forwarding-rule;
                }
            }
        }
    }

    // RULE_DEL

    rpc rule_delete {
        description
        "TBD for input parameters of which RULE_DEL includes
         but now just traffic-descriptor.";
        input {
            list deleting-rule {
                description "Rules that are deleted from an agent";
                uses port-field;

                list target-rule {
                    description "Deleting rules";
                    leaf target-rule-id {
                        type fpcp-rule-id;
                        mandatory true;
                        description "Rule ID";
                    }
                }
            }
        }
    }

    rpc add_dpn {
        input {
            leaf node-id {
                type inet:uri;
            }
            uses carrier;
            uses network;
            uses dpn;
            leaf ip-address {
                type inet:ip-address;
            }
            leaf port {
                type inet:port-number;
            }
        }
    }

    rpc remove_dpn {
        input {
            leaf node-id {
                type inet:uri;
            }
            uses port-field;
            uses dpn;
        }
    }

    // EVENT_REG

    rpc event_register {
        description
        "TBD for registered parameters included in EVENT_REG.";
    }

    // PROBE

    rpc probe {
        description
        "TBD for retrieved parameters included in PROBE.";
    }

    // NOTIFY

    notification notify {
        description
        "TBD for which status and event are reported to client.";
    }

}
