module ietf-dmm-fpcagent {
    namespace "urn:ietf:params:xml:ns:yang:ietf-dmm-fpcagent";
    prefix fpcagent;

    import ietf-dmm-fpcbase { prefix fpcbase; revision-date 2016-08-03; }
    import ietf-inet-types { prefix inet; revision-date 2013-07-15; }

    organization "IETF DMM Working Group";
    contact "Satoru Matsushima <satoru.matsushima@g.softbank.co.jp>";

    description
    "This module contains YANG definition for
     Forwarding Policy Configuration Protocol (FPCP).

     Copyright (c) 2016 IETF Trust and the persons identified as the
     document authors. All rights reserved.

     This document is subject to BCP 78 and the IETF Trust's Legal
     Provisions Relating to IETF Documents
     (http://trustee.ietf.org/license-info) in effect on the date of
     publication of this document. Please review these documents
     carefully, as they describe your rights and restrictions with
     respect to this document. Code Components extracted from this
     document must include Simplified BSD License text as described
     in Section 4.e of the Trust Legal Provisions and are provided
     without warranty as described in the Simplified BSD License.";

    revision 2016-08-03 {
        description "Initial Revision.";
        reference "draft-ietf-dmm-fpc-cpdp-05";
    }
    feature fpc-cloning {
      description "An ability to support cloning in the RPC.";
    }
    feature fpc-basename-registry {
      description "Ability to track Base Names already provisioned on the Agent";
    }
    feature fpc-bundles {
      description "Ability for Client to send multiple bundles of actions to
        an Agent";
    }
    feature fpc-client-binding {
      description "Allows a FPC Client to bind a DPN to an Topology Object";
    }
    feature fpc-auto-binding {
      description "Allows a FPC Agent to advertise Topology Objects that could be DPNs";
    }
    feature instruction-bitset {
      description "Allows the expression of instructions (bit sets) over FPC.";
    }
    feature operation-ref-scope {
      description "Provides the scope of refeneces in an operation.  Used to optmize
        the Agent processing.";
    }

    typedef agent-identifier {
        type fpcbase:fpc-identity;
        description "Agent Identifier";
    }

    typedef client-identifier {
        type fpcbase:fpc-identity;
        description "Client Identifier";
    }

    grouping basename-info {
          leaf basename {
            if-feature fpcagent:fpc-basename-registry;
            type fpcbase:fpc-identity;
            description "Rules Basename";
          }
          leaf base-state {
            if-feature fpcagent:fpc-basename-registry;
            type string;
            description "Current State";
          }
          leaf base-checkpoint {
            if-feature fpcagent:fpc-basename-registry;
            type string;
            description "Checkpoint";
          }
          description "Basename Information";
    }

    // Top Level Structures
    container tenants {
        list tenant {
            key "tenant-id";
            leaf tenant-id {
                type fpcbase:fpc-identity;
                description "Tenant ID";
            }

            container fpc-policy {
              list policy-groups {
                  key "policy-group-id";
                  uses fpcbase:fpc-policy-group;
                  description "Policy Groups";
              }
              list policies {
                  key "policy-id";
                  uses fpcbase:fpc-policy;
                  description "Policies";
              }
              list descriptors {
                key descriptor-id;
                uses fpcbase:fpc-descriptor;
                description "Descriptors";
              }
              list actions {
                  key action-id;
                  uses fpcbase:fpc-action;
                  description "Actions";
              }
              description "Policy";
            }

            container fpc-mobility {
              config false;
              list contexts {
                  key context-id;
                  uses fpcbase:fpc-context;
                  description "Contexts";
              }
              list ports {
                  key port-id;
                  uses fpcbase:fpc-port;
                  description "Ports";
              }
              list monitors {
                  uses fpcbase:monitor-config;
                  description "Monitors";
              }
              description "Mobility";
            }
            container fpc-topology {
              // Basic Agent Topology Structures
              list domains {
                key domain-id;
                uses fpcbase:fpc-domain;
                uses fpcagent:basename-info;
                description "Domains";
              }

              list dpn-group-peers {
                  if-feature fpcbase:fpc-basic-agent;
                  key "remote-dpn-group-id";
                  uses fpcbase:fpc-dpn-peer-group;
                  description "DPN Peer Groups";
              }
              leaf dpn-id {
                if-feature fpcbase:fpc-basic-agent;
                type fpcbase:fpc-dpn-id;
                description "DPN ID";
              }
              leaf-list control-protocols {
                if-feature fpcbase:fpc-basic-agent;
                type identityref {
                  base "fpcbase:fpc-dpn-control-protocol";
                }
                description "Control Protocols";
              }

              list dpn-groups {
                  if-feature fpcbase:fpc-multi-dpn;
                  key dpn-group-id;
                  uses fpcagent:fpc-dpn-group;
                  list domains {
                    key domain-id;
                    uses fpcbase:fpc-domain;
                    uses fpcagent:basename-info;
                    description "Domains";
                  }
                  description "DPN Groups";
              }
              list dpns {
                  if-feature fpcbase:fpc-multi-dpn;
                  key dpn-id;
                  uses fpcbase:fpc-dpn;
                  description "DPNs";
              }
              description "Topology";
            }
          description "Tenant";
        }
        description "Tenant List";
    }

    container fpc-agent-info {
      // General Agent Structures
      leaf-list supported-features {
        type string;
        description "Agent Features";
      }

      // Common Agent Info
      list supported-events {
        key event;
        leaf event {
          type identityref {
            base "fpcbase:event-type";
          }
          description "Event Types";
        }
        leaf event-id {
          type fpcbase:event-type-id;
          description "Event ID";
        }
        description "Supported Events";
      }

      list supported-error-types {
        key error-type;
        leaf error-type {
          type identityref {
            base "fpcagent:error-type";
          }
          description "Error Type";
        }
        leaf error-type-id {
          type fpcagent:error-type-id;
          description "Error Type ID";
        }
        description "Supported Error Types";
      }
      description "General Agent Information";
    }


    // Multi-DPN Agent Structures
    grouping fpc-dpn-group {
        leaf dpn-group-id {
            type fpcbase:fpc-dpn-group-id;
            description "DPN Group ID";
        }
        leaf data-plane-role {
            type identityref {
                base "fpcbase:fpc-forwaridingplane-role";
            }
            description "Dataplane Role";
        }
        leaf access-type {
            type identityref {
                base "fpcbase:fpc-access-type";
            }
            description "Access Type";
        }
        leaf mobility-profile {
            type identityref {
                base "fpcbase:fpc-mobility-profile-type";
            }
            description "Mobility Profile";
        }
        list dpn-group-peers {
            key "remote-dpn-group-id";
            uses fpcbase:fpc-dpn-peer-group;
            description "Peer DPN Groups";
        }
        description "FPC DPN Group";
    }


    // RPC
    // RPC Specific Structures
    //Input Structures
    typedef admin-status {
        type enumeration {
            enum enabled {
              value 0;
              description "enabled";
            }
            enum disabled {
              value 1;
              description "disabled";
            }
            enum virtual {
              value 2;
              description "virtual";
            }
        }
        description "Adminstrative Status";
    }

    typedef session-status {
        type enumeration {
            enum complete {
              value 0;
              description "complete";
            }
            enum incomplete {
              value 1;
              description "incomplete";
            }
            enum outdated {
              value 2;
              description "outdated";
            }
        }
        description "Session Status";
    }

    typedef op-delay {
        type uint32;
        description "Operation Delay (ms)";
    }

    typedef op-identifier {
        type uint64;
        description "Operation Identifier";
    }

    typedef ref-scope {
      type enumeration {
        enum none {
          value 0;
          description "no references";
        }
        enum op {
          value 1;
          description "op - All references are contained in the operation body (intra-op)";
        }
        enum bundle {
          value 2;
          description "bundle - All references in exist in bundle (inter-operation/intra-bundle).
          NOTE - If this value comes in CONFIG call it is equivalen to 'op'.";
        }
        enum storage {
          value 3;
          description "storage - One or more references exist outside of the operation and bundle.
          A lookup to a cache / storage is required.";
        }
        enum unknown {
          value 4;
          description " unknown - the location of the references are unknown.  This is treated as
          a 'storage' type.";
        }
      }
      description "Search scope for references in the operation.";
    }

    grouping instructions {
      container instructions {
        if-feature instruction-bitset;
        choice instr-type {
          description "Instruction Value Choice";
        }
        description "Instructions";
      }
      description "Instructions Value";
    }

    grouping op-header {
      leaf client-id {
        type fpcagent:client-identifier;
        description "Client ID";
      }
      leaf delay {
        type op-delay;
        description "Delay";
      }
      leaf session-state {
        type session-status;
        description "Session State";
      }
      leaf admin-state {
        type admin-status;
        description "Admin State";
      }
      leaf op-type {
        type enumeration {
          enum create {
            value 0;
            description "create";
          }
          enum update {
            value 1;
            description "update";
          }
          enum query {
            value 2;
            description "query";
          }
          enum delete {
            value 3;
            description "delete";
          }
        }
        description "Type";
      }
      leaf op-ref-scope {
          if-feature operation-ref-scope;
          type fpcagent:ref-scope;
          description "Reference Scope";
      }
      uses fpcagent:instructions;
      description "Operation Header";
    }

    grouping clone-ref {
      leaf entity {
        type fpcbase:fpc-identity;
        description "Clone ID";
      }
      leaf source {
        type fpcbase:fpc-identity;
        description "Source";
      }
      description "Clone Reference";
    }

    identity command-set {
      description "protocol specific commands";
    }

    grouping context-operation {
      uses fpcbase:fpc-context;
      uses fpcagent:instructions;
      description "Context Operation";
    }

    // Output Structure
    grouping payload {
      list ports {
        uses fpcbase:fpc-port;
        description "Ports";
      }
      list contexts {
        uses fpcagent:context-operation;
        description "Contexts";
      }
      description "Payload";
    }

    grouping op-input {
      uses fpcagent:op-header;
      leaf op-id {
        type op-identifier;
        description "Operation ID";
      }
      choice op_body {
        case create_or_update {
          list clones {
            if-feature fpc-cloning;
            key entity;
            uses fpcagent:clone-ref;
            description "Clones";
          }
          uses fpcagent:payload;
          description "Create/Update input";
        }
        case delete_or_query {
          uses fpcbase:targets-value;
          description "Delete/Query input";
        }
        description "Opeartion Input value";
      }
      description "Operation Input";
    }

    typedef result {
      type enumeration {
        enum ok {
          value 0;
          description "OK";
        }
        enum err {
          value 1;
          description "Error";
        }
        enum ok-notify-follows {
          value 2;
          description "OK with NOTIFY following";
        }
      }
      description "Result Status";
    }

    identity error-type {
      description "Base Error Type";
    }
    identity name-already-exists {
      description "Notification that an entity of the same name already exists";
    }

    typedef error-type-id {
      type uint32;
      description "Integer form of the Error Type";
    }

    grouping op-status-value {
      leaf op-status {
        type enumeration {
          enum ok {
            value 0;
            description "OK";
          }
          enum err {
            value 1;
            description "Error";
          }
        }
        description "Operation Status";
      }
      description "Operation Status Value";
    }

    grouping error-info {
          leaf error-type-id {
            type fpcagent:error-type-id;
            description "Error ID";
          }
          leaf error-info {
            type string {
              length "1..1024";
            }
            description "Error Detail";
          }
          description "Error Information";
    }

    grouping result-body {
      leaf op-id {
        type op-identifier;
        description "Operation Identifier";
      }
      choice result-type {
        case err {
          uses fpcagent:error-info;
          description "Error Information";
        }
        case create-or-update-success {
          uses fpcagent:payload;
          description "Create/Update Success";
        }
        case delete_or_query-success {
          uses fpcbase:targets-value;
          description "Delete/Query Success";
        }
        case empty-case {
          description "Empty Case";
        }
        description "Result Value";
      }
      description "Result Body";
    }

    // Common RPCs
    rpc configure {
      description "CONF message";
      input {
        uses fpcagent:op-input;
      }
      output {
        leaf result {
          type result;
          description "Result";
        }
        uses fpcagent:result-body;
      }
    }

    rpc configure-bundles {
      if-feature fpcagent:fpc-bundles;
      description "CONF_BUNDLES message";
      input {
        leaf highest-op-ref-scope {
            if-feature operation-ref-scope;
            type fpcagent:ref-scope;
            description "Highest Op-Ref used in the input";
        }
        list bundles {
          key op-id;
          uses fpcagent:op-input;
          description "List of operations";
        }
      }
      output {
        list bundles {
          key op-id;
          uses fpcagent:result-body;
          description "Operation Identifier";
        }
      }
    }

    // Notification Messages & Structures
    typedef notification-id {
      type uint32;
      description "Notification Identifier";
    }

    grouping notification-header {
      leaf notification-id {
          type fpcagent:notification-id;
          description "Notification ID";
      }
      leaf timestamp {
          type uint32;
          description "timestamp";
      }
      description "Notification Header";
    }

    notification config-result-notification {
      uses fpcagent:notification-header;
      choice value {
        case config-result {
          uses fpcagent:op-status-value;
          uses fpcagent:result-body;
          description "CONF Result";
        }
        case config-bundle-result {
          list bundles {
            uses fpcagent:op-status-value;
            uses fpcagent:result-body;
            description "Operation Results";
          }
          description "CONF_BUNDLES Result";
        }
        description "Config Result value";
      }
      description "CONF/CONF_BUNDLES Async Result";
    }

    rpc event_register {
      description "Used to register monitoring of parameters/events";
        input {
          uses fpcbase:monitor-config;
        }
        output {
          leaf monitor-result {
            type fpcagent:result;
            description "Result";
          }
          uses fpcagent:error-info;
        }
    }

    rpc event_deregister {
      description "Used to de-register monitoring of parameters/events";
        input {
          list monitors {
            uses fpcbase:monitor-id;
            description "Monitor ID";
          }
        }
        output {
          leaf monitor-result {
            type fpcagent:result;
            description "Result";
          }
          uses fpcagent:error-info;
        }

    }

    rpc probe {
        description "Probe the status of a registered monitor";
        input {
          uses fpcbase:targets-value;
        }
        output {
          leaf monitor-result {
            type fpcagent:result;
            description "Result";
          }
          uses fpcagent:error-info;
        }
    }

    notification notify {
        uses fpcagent:notification-header;
        choice value {
            case dpn-candidate-available {
              if-feature fpcagent:fpc-auto-binding;
              leaf node-id {
                type inet:uri;
                description "Topology URI";
              }
              leaf-list access-types {
                type identityref {
                  base "fpcbase:fpc-access-type";
                }
                description "Access Types";
              }
              leaf-list mobility-profiles {
                type identityref {
                  base "fpcbase:fpc-mobility-profile-type";
                }
                description "Mobility Profiles";
              }
              leaf-list forwarding-plane-roles {
                type identityref {
                  base "fpcbase:fpc-forwaridingplane-role";
                }
                description "Forwarding Plane Role";
              }
              description "DPN Candidate Availability";
            }
            case monitor-notification {
              choice monitor-notification-value {
                case simple-monitor {
                  uses fpcbase:report;
                  description "Report";
                }
                case bulk-monitors {
                  list reports {
                    uses fpcbase:report;
                    description "Reports";
                  }
                  description "Bulk Monitor Response";
                }
                description "Monitor Notification value";
              }
              description "Monitor Notification";
            }
            description "Notify Value";
        }
        description "Notify Message";
    }
}
